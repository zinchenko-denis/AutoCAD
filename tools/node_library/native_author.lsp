; Universal native authoring runtime. Input afn:data is supplied by generate.py.
; Requires full Windows AutoCAD 2024, Unicode AutoLISP (LISPSYS 1 or 2).
; This source has not been executed in an AutoCAD host in the Linux check.
(vl-load-com)

(defun afn:get (key data) (cdr (assoc key data)))
(defun afn:pt (p) (list (car p) (cadr p) 0.0))
(defun afn:fail (message)
  (setq afn:failure message)
  (exit))
(defun afn:assert (ok message) (if (not ok) (afn:fail message)))
(defun afn:at (stage)
  ; Diagnostics are dynamically bound by our command, not inferred after cleanup.
  (setq afn:stage stage afn:last-command nil)
  (princ (strcat "\n[AFN] " stage)))
(defun afn:unbox (x)
  (cond ((= (type x) 'VARIANT) (afn:unbox (vlax-variant-value x)))
        ((= (type x) 'SAFEARRAY) (mapcar 'afn:unbox (vlax-safearray->list x)))
        (T x)))
(defun afn:command-result (result)
  ; Snapshot the failed native prompt before any cleanup can overwrite it.
  (if (or (vl-catch-all-error-p result) (/= 0 (logand 3 (getvar "CMDACTIVE"))))
    (progn
      (setq afn:failed-prompt (getvar "LASTPROMPT"))
      (afn:fail (if (vl-catch-all-error-p result)
        (vl-catch-all-error-message result)
        (strcat "Command did not finish: " afn:last-command))))))
(defun afn:cmd (arguments / result)
  (setq afn:last-command (car arguments))
  ; Every call is one complete non-interactive command. command-s cancels an
  ; incomplete token stream in its temporary processor; it cannot leave the
  ; next command name serving as an answer to an unfinished native prompt.
  (setq result (vl-catch-all-apply 'command-s arguments))
  (afn:command-result result))
(defun afn:open-editor (name / result)
  ; afn:editor-owned is deliberately dynamically bound by ATFNATIVEBUILD.
  ; Its preflight proved that no foreign Block Editor was open.
  (setq afn:last-command "_.-BEDIT")
  (setq result (vl-catch-all-apply 'command-s (list "_.-BEDIT" name)))
  ; BEDIT may enter the editor before reporting an error. Record ownership
  ; from the readback while preflight still proves there was no foreign editor.
  (if (= (getvar "BLOCKEDITOR") 1) (setq afn:editor-owned T))
  (afn:command-result result)
  (afn:assert (and afn:editor-owned (= 0 (logand 3 (getvar "CMDACTIVE")))) "BEDIT did not open cleanly"))
(defun afn:close-editor ()
  (afn:cmd '("_.BSAVE"))
  (afn:cmd '("_.BCLOSE"))
  (afn:assert (= (getvar "BLOCKEDITOR") 0) "Our Block Editor did not close")
  (setq afn:editor-owned nil))
(defun afn:sort (values)
  ; vl-sort removes duplicates; sort indices to preserve repeated geometry.
  (mapcar '(lambda (i) (nth i values))
    (vl-sort-i values '(lambda (a b) (< (vl-prin1-to-string a) (vl-prin1-to-string b))))))
(defun afn:property (reference name / found prop)
  (foreach prop (vlax-invoke reference 'GetDynamicBlockProperties)
    (if (= (vla-get-PropertyName prop) name)
      (progn (afn:assert (null found) (strcat "Duplicate property: " name)) (setq found prop))))
  (afn:assert found (strcat "Missing native property: " name))
  found)
(defun afn:value (reference name)
  (afn:unbox (vla-get-Value (afn:property reference name))))
(defun afn:set (reference name value / prop old)
  (setq prop (afn:property reference name) old (vla-get-Value prop))
  (afn:assert (= :vlax-false (vla-get-ReadOnly prop)) (strcat "Read-only property: " name))
  (vla-put-Value prop (vlax-make-variant value (vlax-variant-type old)))
  (vla-Update reference)
  ; ActiveX can silently ignore an out-of-range assignment. Always read it back.
  (afn:assert (equal value (afn:value reference name) 1e-7) (strcat "Native setter rejected: " name)))
(defun afn:apply (reference state / entry)
  ; Discrete state first. Recheck the final property tuple after every action
  ; has evaluated, so a later property cannot silently invalidate an earlier one.
  (afn:set reference "AFN_VARIANT" (afn:get "AFN_VARIANT" state))
  (afn:set reference "AFN_INSULATION" (afn:get "AFN_INSULATION" state))
  (afn:set reference "AFN_CLADDING_X" (afn:get "AFN_CLADDING_X" state))
  (foreach entry state
    (afn:assert (equal (cdr entry) (afn:value reference (car entry)) 1e-7)
      (strcat "Final native property tuple mismatch: " (car entry)))))
(defun afn:insert (space name position scale rotation)
  (vla-InsertBlock space (vlax-3d-point position) name scale scale scale rotation))
(defun afn:signature (reference / properties prop values name)
  (afn:assert (= :vlax-true (vla-get-IsDynamicBlock reference)) "Definition is not a native dynamic block")
  (setq properties (vlax-invoke reference 'GetDynamicBlockProperties))
  (afn:assert (= (length properties) 3) "Expected exactly three native dynamic properties")
  (foreach name '("AFN_INSULATION" "AFN_CLADDING_X")
    (setq prop (afn:property reference name))
    (afn:assert (and (= :vlax-false (vla-get-ReadOnly prop)) (numberp (afn:value reference name)))
      (strcat "Writable numeric property required: " name)))
  (setq prop (afn:property reference "AFN_VARIANT") values (afn:unbox (vla-get-AllowedValues prop)))
  (afn:assert (= :vlax-false (vla-get-ReadOnly prop)) "Visibility property is read-only")
  (afn:assert (equal (afn:sort values) (afn:sort (afn:get "variants" afn:data)))
    "Visibility allowed values do not match the two variants"))

(defun afn:make (entry / kind common data entity point obj tag previous)
  (setq kind (afn:get "type" entry)
    common (list '(8 . "0") (cons 62 (cond ((afn:get "color" entry)) (T 256)))))
  (cond
    ((= kind "line")
      (setq data (append '((0 . "LINE")) common
        (list (cons 10 (afn:pt (afn:get "start" entry))) (cons 11 (afn:pt (afn:get "end" entry)))))))
    ((= kind "polyline")
      (setq data (append '((0 . "LWPOLYLINE") (100 . "AcDbEntity")) common
        (list '(100 . "AcDbPolyline") (cons 90 (length (afn:get "points" entry)))
          (cons 70 (if (afn:get "closed" entry) 1 0)))))
      (foreach point (afn:get "points" entry) (setq data (append data (list (cons 10 point))))))
    ((= kind "circle")
      (setq data (append '((0 . "CIRCLE")) common
        (list (cons 10 (afn:pt (afn:get "center" entry))) (cons 40 (afn:get "radius" entry))))))
    ((= kind "text")
      (setq data (append '((0 . "TEXT")) common
        (list (cons 10 (afn:pt (afn:get "position" entry))) (cons 40 (afn:get "height" entry))
          (cons 1 (afn:get "text" entry)) '(7 . "Standard") '(50 . 0.0)))))
    ((= kind "attribute")
      (setq tag (afn:get "tag" entry)
        data (append '((0 . "ATTDEF") (100 . "AcDbEntity")) common
          (list '(100 . "AcDbText") (cons 10 (afn:pt (afn:get "position" entry)))
            (cons 40 (afn:get "height" entry)) (cons 1 (afn:get "text" entry))
            '(7 . "Standard") '(50 . 0.0) '(100 . "AcDbAttributeDefinition")
            '(280 . 0) (cons 3 (cond ((afn:get "prompt" entry)) (T tag)))
            (cons 2 tag) '(70 . 0) '(73 . 0) '(74 . 0) '(280 . 1)))))
    ((= kind "dimension")
      (setq previous (entlast))
      (afn:cmd (list "_.DIMALIGNED" "_non" (afn:pt (afn:get "p1" entry))
        "_non" (afn:pt (afn:get "p2" entry)) "_non" (afn:pt (afn:get "line_point" entry))))
      (setq entity (entlast))
      (afn:assert (and entity (not (equal previous entity))) "DIMALIGNED created no new object")
      (setq obj (vlax-ename->vla-object entity))
      (afn:assert (= (vla-get-ObjectName obj) "AcDbAlignedDimension") "DIMALIGNED did not create a dimension")
      ; A template's DIMLFAC / DIMPOST must not relabel millimetres silently.
      (vla-put-LinearScaleFactor obj 1.0)
      (vla-put-ScaleFactor obj 1.0)
      (vla-put-Layer obj "0")
      (vla-put-RoundDistance obj 0.0)
      (vla-put-ToleranceDisplay obj 0)
      (vla-put-TextOverride obj "")
      (vla-put-TextPrefix obj "")
      (vla-put-TextSuffix obj "")
      (vla-put-AltUnits obj :vlax-false)
      (vla-put-UnitsFormat obj 2)
      (vla-put-PrimaryUnitsPrecision obj 8)
      (vla-put-SuppressTrailingZeros obj :vlax-true)
      (vla-put-TextHeight obj (cond ((afn:get "height" entry)) (T 3.0)))
      (vla-put-ArrowheadSize obj (cond ((afn:get "height" entry)) (T 3.0)))
      (vla-put-Color obj (cond ((afn:get "color" entry)) (T 256)))))
  (if data (progn (afn:assert (entmake data) (strcat "Cannot create: " (afn:get "id" entry))) (setq entity (entlast))))
  (afn:assert entity "Entity construction returned no object")
  ; Standard XData identifies the precise bound dimension after native evaluation.
  ; Missing/duplicate IDs fail the host check instead of guessing by measurement.
  (afn:assert (or (tblsearch "APPID" "AF_NODE_ENTITY") (regapp "AF_NODE_ENTITY"))
    "Cannot register source entity IDs")
  (afn:assert (entmod (append (entget entity)
    (list (list -3 (list "AF_NODE_ENTITY" (cons 1000 (afn:get "id" entry)))))))
    "Cannot attach source entity ID")
  entity)
(defun afn:set-of (ids entities / result ident object)
  (setq result (ssadd))
  (foreach ident ids
    (setq object (cdr (assoc ident entities)))
    (afn:assert (and object (entget object)) (strcat "Missing authoring entity: " ident))
    (ssadd object result))
  result)
(defun afn:build-definition (name space / old-state reference entities entry parameters name-p spec ename action frame selected variants variant ids previous)
  ; Begin with an empty, exclusively owned definition. Never redefine an existing name.
  (afn:assert (entmake (list '(0 . "BLOCK") (cons 2 name) '(70 . 0) '(10 0.0 0.0 0.0))) "Cannot create block header")
  (afn:assert (entmake '((0 . "ENDBLK"))) "Cannot close block header")
  (afn:at "create visibility parameter")
  (afn:open-editor name)
  ; Visibility, like Linear below, ends with the number-of-grips prompt.
  (afn:cmd (list "_.BPARAMETER" "_Visibility" "_Name" "AFN_VARIANT" "_Label" "AFN_VARIANT" '(0.0 -100.0 0.0) 1))
  (afn:close-editor)
  ; Read the localized default state through the native reference API.
  ; No hard-coded English/Russian VisibilityState0 name and no private DXF internals.
  (setq reference (afn:insert space name '(0.0 0.0 0.0) 1.0 0.0))
  (afn:assert (= :vlax-true (vla-get-IsDynamicBlock reference)) "Visibility parameter was not created")
  (setq old-state (afn:value reference "AFN_VARIANT"))
  (vla-Delete reference)
  (afn:open-editor name)
  (foreach entry (afn:get "entities" afn:data)
    (afn:at (strcat "entity " (afn:get "id" entry)))
    (setq entities (cons (cons (afn:get "id" entry) (afn:make entry)) entities)))
  (foreach entry (afn:get "parameters" afn:data)
    (setq name-p (car entry) spec (cdr entry) previous (entlast))
    (afn:at (strcat "linear parameter " name-p))
    (afn:cmd (list "_.BPARAMETER" "_Linear" "_Name" name-p "_Label" name-p
      "_Base" "_Startpoint" "_Palette" "_Yes"
      (afn:pt (afn:get "start" spec)) (afn:pt (afn:get "end" spec)) (afn:pt (afn:get "label" spec)) 1))
    (setq ename (entlast))
    (afn:assert (and ename (not (equal previous ename))) (strcat "BPARAMETER created no new object: " name-p))
    (setq parameters (cons (cons name-p ename) parameters)))
  (foreach action (afn:get "actions" afn:data)
    (setq name-p (afn:get "parameter" action) ename (cdr (assoc name-p parameters))
      spec (afn:get name-p (afn:get "parameters" afn:data))
      selected (afn:set-of (afn:get "entities" action) entities))
    (afn:at (strcat "action " name-p " / " (afn:get "kind" action)))
    (if (= (afn:get "kind" action) "stretch")
      (progn
        (setq frame (afn:get "frame" action))
        (afn:cmd (list "_.BACTIONTOOL" "_Stretch" (list ename (afn:pt (afn:get "label" spec)))
          (afn:pt (afn:get "end" spec)) (afn:pt (car frame)) (afn:pt (cadr frame)) selected "")))
      (afn:cmd (list "_.BACTIONTOOL" "_Move" (list ename (afn:pt (afn:get "label" spec)))
        (afn:pt (afn:get "end" spec)) selected ""))))
  (setq variants (afn:get "variants" afn:data))
  (foreach variant variants
    (afn:at (strcat "visibility state " variant))
    (afn:cmd (list "_.-BVSTATE" "_New" variant "_Hide"))
    (setq ids nil)
    (foreach entry (afn:get "entities" afn:data)
      (if (or (null (afn:get "variant" entry)) (= (afn:get "variant" entry) variant))
        (setq ids (cons (afn:get "id" entry) ids))))
    (afn:cmd (list "_.BVSHOW" (afn:set-of ids entities) "" "_Current")))
  (afn:cmd (list "_.-BVSTATE" "_Set" (car variants)))
  (afn:assert (not (member old-state variants)) "Unexpected collision with native default visibility state")
  (afn:cmd (list "_.-BVSTATE" "_Delete" old-state))
  (afn:close-editor))

(defun afn:read-properties (object names / result key)
  (foreach key names
    (afn:assert (vlax-property-available-p object key) (strcat "Unsupported native snapshot property: " (vl-symbol-name key)))
    (setq result (cons (afn:unbox (vlax-get-property object key)) result)))
  (reverse result))
(defun afn:entity-snapshot (object / kind fields ident)
  (setq kind (vla-get-ObjectName object))
  (setq ident (cdr (assoc 1000 (cdr (cadr (assoc -3
    (entget (vlax-vla-object->ename object) '("AF_NODE_ENTITY"))))))))
  (setq fields
    (cond ((= kind "AcDbLine") '(StartPoint EndPoint))
          ((= kind "AcDbPolyline") '(Coordinates Closed Elevation))
          ((= kind "AcDbCircle") '(Center Radius))
          ((= kind "AcDbText") '(InsertionPoint TextString Height Rotation))
          ((= kind "AcDbAttributeDefinition") '(InsertionPoint TagString TextString Height Rotation))
          ((= kind "AcDbAlignedDimension") '(ExtLine1Point ExtLine2Point Measurement TextPosition TextOverride LinearScaleFactor TextPrefix TextSuffix UnitsFormat RoundDistance ToleranceDisplay PrimaryUnitsPrecision AltUnits Layer))
          (T (afn:fail (strcat "Unsupported native exploded object: " kind)))))
  (cons kind (cons ident (afn:read-properties object fields))))
(defun afn:attributes (reference / result object)
  (if (= :vlax-true (vla-get-HasAttributes reference))
    (foreach object (vlax-invoke reference 'GetAttributes)
      (setq result (cons (afn:read-properties object '(TagString TextString InsertionPoint Height Rotation)) result))))
  (afn:sort result))
(defun afn:snapshot (reference / geometry object exploded props name)
  ; Explode returns temporary, native-evaluated geometry. Delete every temporary
  ; object; the original reference, its dynamic definition and siblings are unchanged.
  (setq exploded (vlax-invoke reference 'Explode))
  (foreach object exploded (setq geometry (cons (afn:entity-snapshot object) geometry)) (vla-Delete object))
  (foreach name '("AFN_INSULATION" "AFN_CLADDING_X" "AFN_VARIANT")
    (setq props (cons (cons name (afn:value reference name)) props)))
  (list (afn:sort geometry) (reverse props) (afn:attributes reference)
    (afn:read-properties reference '(InsertionPoint XScaleFactor YScaleFactor ZScaleFactor Rotation))))
(defun afn:geometry-only (snapshot / result entity)
  (foreach entity (car snapshot)
    (if (member (car entity) '("AcDbLine" "AcDbPolyline" "AcDbCircle")) (setq result (cons entity result))))
  result)
(defun afn:dimensions-only (snapshot / result entity)
  (foreach entity (car snapshot)
    (if (= (car entity) "AcDbAlignedDimension") (setq result (cons entity result))))
  result)
(defun afn:marks-only (snapshot / result entity)
  (foreach entity (car snapshot)
    (if (= (car entity) "AcDbText") (setq result (cons entity result))))
  result)
(defun afn:check-dimensions (snapshot / entry name ident matches entity value)
  ; Used on the identity-transformed probe. Coordinate movement alone cannot pass:
  ; the exact bound dimension must visibly measure the final parameter value.
  (foreach entry (afn:get "parameters" afn:data)
    (setq name (car entry) ident (afn:get "dimension_id" (cdr entry)) matches nil
      value (afn:get name (cadr snapshot)))
    (foreach entity (afn:dimensions-only snapshot)
      (if (equal (cadr entity) ident) (setq matches (cons entity matches))))
    (afn:assert (= (length matches) 1) (strcat "Expected one visible bound dimension: " ident))
    (setq entity (car matches))
    (afn:assert (and (equal value (nth 4 entity) 1e-7)
      (equal value (distance (nth 2 entity) (nth 3 entity)) 1e-7))
      (strcat "Bound dimension measurement mismatch: " name " / " ident))
    (afn:assert (and (= (nth 6 entity) "") (equal (nth 7 entity) 1.0 1e-7)
      (= (nth 8 entity) "") (= (nth 9 entity) "") (= (nth 10 entity) 2)
      (equal (nth 11 entity) 0.0 1e-7) (= (nth 12 entity) 0)
      (= (nth 13 entity) 8) (= (nth 14 entity) :vlax-false) (= (nth 15 entity) "0"))
      (strcat "Bound dimension display format mismatch: " ident))))
(defun afn:probe-one (reference / before after defaults alternate name)
  (setq defaults (afn:get "defaults" afn:data) alternate (afn:get "alternate" afn:data))
  (afn:apply reference defaults)
  (setq before (afn:snapshot reference))
  (afn:check-dimensions before)
  (foreach name '("AFN_INSULATION" "AFN_CLADDING_X" "AFN_VARIANT")
    (afn:at (strcat "native evaluation " name))
    (afn:set reference name (afn:get name alternate))
    (setq after (afn:snapshot reference))
    (afn:check-dimensions after)
    (afn:assert (not (equal (afn:geometry-only before) (afn:geometry-only after) 1e-7))
      (strcat "Property changed but native geometry did not: " name))
    (if (= name "AFN_VARIANT")
      (afn:assert (not (equal (afn:marks-only before) (afn:marks-only after) 1e-7)) "Visibility did not change the native marks")
      (afn:assert (not (equal (afn:dimensions-only before) (afn:dimensions-only after) 1e-7))
        (strcat "Native dimension did not change: " name)))
    (afn:set reference name (afn:get name defaults))
    (afn:assert (equal before (afn:snapshot reference) 1e-7) (strcat "Roundtrip drift: " name))))
(defun afn:five (space name / refs reference index positions scales rotations before after copy snapshot)
  (setq positions '((0.0 0.0 0.0) (1200.0 0.0 0.0) (2400.0 0.0 0.0) (3600.0 0.0 0.0) (4800.0 0.0 0.0))
    scales '(1.0 1.0 2.0 1.0 1.0) rotations (list 0.0 (/ pi 2.0) (/ pi 6.0) 0.0 pi) index 0)
  (repeat 5
    (setq reference (afn:insert space name (nth index positions) (nth index scales) (nth index rotations)))
    (afn:signature reference)
    (afn:apply reference (afn:get "defaults" afn:data))
    (setq refs (append refs (list reference)) index (1+ index)))
  (afn:probe-one (car refs))
  (afn:at "native 3-of-5 transition")
  (setq before (mapcar 'afn:snapshot refs) index 0)
  (foreach reference refs
    (if (< index 3) (afn:apply reference (afn:get "alternate" afn:data)))
    (setq index (1+ index)))
  (setq after (mapcar 'afn:snapshot refs) index 0)
  (afn:check-dimensions (car after))
  (repeat 5
    (if (< index 3)
      (progn
        (afn:assert (not (equal (car (nth index before)) (car (nth index after)) 1e-7)) "Selected instance geometry did not change")
        (afn:assert (equal (cddr (nth index before)) (cddr (nth index after)) 1e-7) "Attribute or insertion transform changed"))
      (afn:assert (equal (nth index before) (nth index after) 1e-7) "Unselected instance changed"))
    (setq index (1+ index)))
  ; Repeat B, return to A, and return to B. No accumulated shifts.
  (afn:at "native repeat and reverse transition")
  (foreach reference (list (nth 0 refs) (nth 1 refs) (nth 2 refs))
    (afn:apply reference (afn:get "alternate" afn:data)))
  (afn:assert (equal after (mapcar 'afn:snapshot refs) 1e-7) "Repeated assignment drift")
  (foreach reference refs (afn:apply reference (afn:get "defaults" afn:data)))
  (afn:assert (equal before (mapcar 'afn:snapshot refs) 1e-7) "Five-instance reverse transition drift")
  (foreach reference (list (nth 0 refs) (nth 1 refs) (nth 2 refs))
    (afn:apply reference (afn:get "alternate" afn:data)))
  (afn:assert (equal after (mapcar 'afn:snapshot refs) 1e-7) "Five-instance second transition drift")
  ; Native database Copy is tested here; the UI COPY/UNDO and save/open are a separate host check.
  (afn:at "native database Copy")
  (setq reference (car refs) snapshot (afn:snapshot reference) copy (vla-Copy reference))
  (afn:assert (equal snapshot (afn:snapshot copy) 1e-7) "Native copied block differs")
  (afn:apply copy (afn:get "defaults" afn:data))
  (afn:assert (equal snapshot (afn:snapshot reference) 1e-7) "Copy modification affected original")
  (vla-Delete copy)
  refs)
(defun afn:marker (document name / block dictionary record values entity readback)
  (setq block (vla-Item (vla-get-Blocks document) name)
    dictionary (vlax-vla-object->ename (vla-GetExtensionDictionary block)))
  (afn:assert (null (dictsearch dictionary "AF_NODE_LIBRARY")) "Definition marker already exists")
  (setq values (append
    (list (cons 1 (afn:get "node_id" afn:data)) (cons 90 (afn:get "version" afn:data)))
    (mapcar '(lambda (v) (cons 1 v))
      (append '("AFN_INSULATION" "AFN_CLADDING_X" "AFN_VARIANT") (afn:get "variants" afn:data)))))
  (setq entity (entmakex (append '((0 . "XRECORD") (100 . "AcDbXrecord") (280 . 1)) values)))
  (afn:assert entity "Cannot create native definition marker")
  (afn:assert (dictadd dictionary "AF_NODE_LIBRARY" entity) "Cannot attach native definition marker")
  (setq readback (vl-remove-if-not '(lambda (x) (member (car x) '(1 90))) (entget entity)))
  (afn:assert (equal values readback) "Native marker readback mismatch"))
(defun afn:restore (settings / entry)
  (foreach entry settings (vl-catch-all-apply 'setvar (list (car entry) (cdr entry)))))

(defun afn:undo-status (flags)
  (strcat "UNDOCTL=" (itoa flags)
    " (запись: " (if (= 1 (logand 1 flags)) "включена" "выключена")
    "; One: " (if (= 2 (logand 2 flags)) "да" "нет")
    "; активная группа: " (if (= 8 (logand 8 flags)) "да" "нет") ")"))
(defun afn:check-drawing (document space name / layer-zero)
  ; Only window/view changes are benign. An explicit whitelist also rejects
  ; unknown future bits, symbol-table changes and modified database variables.
  (princ (strcat "\n[AFN] " (afn:undo-status (getvar "UNDOCTL"))
    "; DBMOD=" (itoa (getvar "DBMOD"))
    "; DWGTITLED=" (itoa (getvar "DWGTITLED"))
    "; BLOCKEDITOR=" (itoa (getvar "BLOCKEDITOR"))))
  (afn:assert (= 0 (logand 3 (getvar "CMDACTIVE")))
    "Завершите текущую команду перед запуском автора узла.")
  (afn:assert (= 0 (getvar "BLOCKEDITOR")) "Закройте редактор блока перед запуском автора.")
  (afn:assert (and (= 0 (getvar "DWGTITLED"))
      (member (getvar "DBMOD") '(0 8 16 24)) (= 1 (getvar "TILEMODE")))
    "Нужен новый несохранённый чертёж модели без изменений данных. Допускаются только изменения окна/вида (DBMOD 0, 8, 16 или 24).")
  (afn:assert (= 0 (logand 8 (getvar "UNDOCTL")))
    "Уже активна группа UNDO. Автор её не закрывает. Завершите прежнюю операцию её штатным способом или откройте отдельный новый чертёж.")
  (setq layer-zero (vla-Item (vla-get-Layers document) "0"))
  (afn:assert (and (= :vlax-true (vla-get-LayerOn layer-zero))
    (= :vlax-false (vla-get-Freeze layer-zero)) (= :vlax-false (vla-get-Lock layer-zero)))
    "Слой 0 должен быть включён, разморожен и разблокирован в новом чертеже.")
  (afn:assert (= 0 (vla-get-Count space)) "Пространство модели должно быть пустым.")
  (afn:assert (null (tblsearch "BLOCK" name)) "Определение с таким именем уже существует; автор его не заменяет."))
(defun afn:prepare-undo (/ flags)
  ; Caller has checked the new/empty DWG and the chosen output. Never close a
  ; group we do not own. Off and One expose different native command prompts.
  (setq flags (getvar "UNDOCTL"))
  (afn:assert (= 0 (logand 8 flags))
    (strcat "Нельзя подготовить отмену: " (afn:undo-status flags)))
  (if (/= 1 (logand 1 flags))
    (afn:cmd '("_.UNDO" "_All"))
    (if (= 2 (logand 2 flags)) (afn:cmd '("_.UNDO" "_Control" "_All"))))
  ; Read back instead of assuming that AutoCAD accepted a setting. Retain All:
  ; restoring Off/One would discard the undo history needed by the new drawing.
  (princ (strcat "\n[AFN] После подготовки: " (afn:undo-status (getvar "UNDOCTL"))
    "; DBMOD=" (itoa (getvar "DBMOD"))))
  (afn:assert (= 1 (logand 11 (getvar "UNDOCTL")))
    "AutoCAD не включил полную запись отмены без активной группы. Построение не начато.")
  (if (/= 1 (logand 3 flags))
    (princ "\n[AFN] Для нового чертежа включён UNDO All. Этот режим сохраняется для последующей отмены.")))

(defun c:ATFNATIVEBUILD (/ *error* document space name output settings settings-changed undo-state undo-result commands-owned afn:editor-owned afn:geometry-started afn:stage afn:last-command afn:failed-prompt refs setting)
  (setq afn:failure nil undo-state nil commands-owned nil settings-changed nil afn:editor-owned nil afn:geometry-started nil afn:stage "preflight" afn:last-command nil afn:failed-prompt nil)
  (princ "\n[AFN] Автор узла 2026-10-08.2")
  (defun *error* (message / result failed-prompt)
    (setq failed-prompt (if afn:failed-prompt afn:failed-prompt (getvar "LASTPROMPT")))
    ; Report first: a cleanup failure must never conceal the original cause.
    (princ (strcat "\nAFN BUILD ABORTED: " (if afn:failure afn:failure message)))
    (princ (strcat "\nAFN STAGE: " afn:stage))
    (if afn:last-command (princ (strcat "\nAFN COMMAND: " afn:last-command)))
    (if failed-prompt (princ (strcat "\nAFN LAST PROMPT: " failed-prompt)))
    ; command is forbidden here and command-s with no arguments is NOT a
    ; documented way to cancel the main document processor. Never run UNDO
    ; while an unknown command is active. Our complete command-s batches use
    ; their own temporary processor, so normal failure cleanup starts idle.
    (if (and commands-owned (= 0 (logand 3 (getvar "CMDACTIVE"))))
      (progn
        (if (and afn:editor-owned (= (getvar "BLOCKEDITOR") 1))
          (progn
            (vl-catch-all-apply 'command-s '("_.BCLOSE" "_Discard"))
            (if (= (getvar "BLOCKEDITOR") 0) (setq afn:editor-owned nil))))
        (if (and (equal undo-state "open") (= (getvar "BLOCKEDITOR") 0)
            (= 0 (logand 3 (getvar "CMDACTIVE"))) (= 8 (logand 8 (getvar "UNDOCTL"))))
          (progn
            (setq result (vl-catch-all-apply 'command-s '("_.UNDO" "_End")))
            ; End can close our group and still report an error. The native
            ; readback, not the return value alone, determines its ownership.
            (if (= 1 (logand 11 (getvar "UNDOCTL")))
              (setq undo-state "ended"))))
        (if (and (equal undo-state "ended") (= (getvar "BLOCKEDITOR") 0)
            (= 0 (logand 3 (getvar "CMDACTIVE"))) (= 1 (logand 11 (getvar "UNDOCTL")))
            ; Attempt flags do not prove a database mutation: the first setvar
            ; or BLOCK entmake may fail before changing anything. Preflight
            ; proved this named definition absent; its actual existence is the
            ; owned mutation witness. Settings alone are restored below, never
            ; by U that could consume history preceding an empty group.
            name (tblsearch "BLOCK" name))
          (vl-catch-all-apply 'command-s '("_.U")))))
    (if settings-changed (vl-catch-all-apply 'afn:restore (list settings)))
    (if afn:geometry-started
      (princ "\nСоздание библиотеки не подтверждено. Незавершённый результат не использовать. Если откат прервался, закройте этот новый чертёж без сохранения.")
      (princ "\nПостроение узла не начато. Устраните указанную причину и повторите запуск."))
    (if (and commands-owned (/= 0 (logand 3 (getvar "CMDACTIVE"))))
      (princ "\nАктивная команда не завершилась; автоматический откат не выполнялся. Завершите её клавишей Esc. Незавершённый новый чертёж не сохраняйте."))
    (princ))
  (afn:assert afn:data "Загрузите сгенерированный LISP узла, а не отдельный служебный runtime.")
  (afn:assert (member (getvar "LISPSYS") '(1 2)) "Нужен Unicode AutoLISP: LISPSYS 1 или 2, затем перезапуск AutoCAD.")
  (setq document (vla-get-ActiveDocument (vlax-get-acad-object)) space (vla-get-ModelSpace document)
    name (afn:get "block_name" afn:data))
  (afn:check-drawing document space name)
  (setq output (getfiled "Сохранить НОВУЮ приватную библиотеку DWG" (strcat name ".dwg") "dwg" 1))
  (afn:assert output "Отмена до изменения чертежа.")
  (afn:assert (null (findfile output)) "Этот DWG уже существует. Выберите новое имя; перезапись запрещена.")
  ; Revalidate after the dialog, before any setting/command changes. Later
  ; DBMOD changes belong to our own commands and are not an input rejection.
  (afn:check-drawing document space name)
  (foreach setting '("CMDECHO" "OSMODE" "SNAPMODE" "BACTIONBARMODE" "DYNMODE" "DIMASSOC" "ATTREQ" "ATTDIA" "INSUNITS" "CLAYER" "DIMLAYER")
    (setq settings (cons (cons setting (getvar setting)) settings)))
  (setq commands-owned T)
  (afn:at "подготовка UNDO")
  (afn:prepare-undo)
  ; As with BEDIT, native commands can mutate state before raising an error.
  ; Preparation proved no group was open, so record a newly opened group
  ; before reporting the command failure. Never claim an initial foreign group.
  (setq afn:last-command "_.UNDO"
    undo-result (vl-catch-all-apply 'command-s '("_.UNDO" "_Begin")))
  (if (= 8 (logand 8 (getvar "UNDOCTL"))) (setq undo-state "open"))
  (afn:command-result undo-result)
  (afn:assert (equal undo-state "open")
    "AutoCAD не открыл группу UNDO автора. Построение не начато.")
  (setq settings-changed T)
  (foreach setting '(("CMDECHO" . 0) ("OSMODE" . 0) ("SNAPMODE" . 0) ("BACTIONBARMODE" . 1)
      ("DYNMODE" . 0) ("DIMASSOC" . 1) ("ATTREQ" . 0) ("ATTDIA" . 0) ("INSUNITS" . 4) ("CLAYER" . "0") ("DIMLAYER" . "0"))
    (setvar (car setting) (cdr setting)))
  (setq afn:geometry-started T)
  (afn:build-definition name space)
  (afn:at "five-instance native checks")
  (setq refs (afn:five space name))
  ; Compatibility is stamped only after native dynamic evaluation passed.
  (afn:at "definition marker")
  (afn:marker document name)
  (afn:restore settings)
  (setvar "INSUNITS" 4)
  (vla-Regen document 1)
  (afn:cmd '("_.ZOOM" "_Extents"))
  (setq afn:last-command "_.UNDO"
    undo-result (vl-catch-all-apply 'command-s '("_.UNDO" "_End")))
  (if (= 1 (logand 11 (getvar "UNDOCTL"))) (setq undo-state "ended"))
  (afn:command-result undo-result)
  (afn:assert (equal undo-state "ended")
    "AutoCAD не завершил группу UNDO автора. Сохранение не выполняется.")
  (afn:at "save DWG")
  (vla-SaveAs document output)
  (setq undo-state nil commands-owned nil)
  (princ (strcat "\nSaved native library: " output))
  (princ "\nPASS IN THIS HOST: native signature/actions/dimensions/marks, five instances (3 changed/2 unchanged), A-B-A-B, repeat, database Copy.")
  (princ "\nSTILL REQUIRED: manual grips/Properties, plugin selection command and cancel/Undo, UI COPY, save-close-open inspection in AutoCAD 2024.")
  (princ))
(princ "\nАвтор узла 2026-10-08.2 загружен; построение ещё не выполнялось. Команда ATFNATIVEBUILD — в новом пустом несохранённом чертеже AutoCAD 2024.")
(princ)
